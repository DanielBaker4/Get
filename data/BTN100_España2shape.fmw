FME workspace BTN100_España2shape.fmw

Parameters:
- SourceDataset_POSTGIS = BTN100   # Source PostGIS Dataset
- FEATURE_TYPES = public.BTN100_0601L_AUTOVIA
- DestDataset_SHAPE = $(FME_MF_DIR)20150713   # Destination ESRI Shape Directory

Readers:
- POSTGIS_1: POSTGIS from $(SourceDataset_POSTGIS) in EPSG:4258

Writers:
- SHAPE_1: SHAPE to $(DestDataset_SHAPE) in LL-ETRS89

public.BTN100_0703S_CEN_ELEC (reader POSTGIS_1)
    attributes: ID_BTN100 int4, ID_SIMPLE int4, ID_CODIGO varchar(5), ID_MOD int4, FECHA_ALTA date, FECHA_BAJA date, TIPO_0703 varchar(2), ETIQUETA varchar(254), COMPO_0705 varchar(2), TIPO_0307 varchar(2), TIPO_0505 varchar(2), COD_1002 varchar(254), ALTITUD float8, LONGITUD varchar(254), CURSO varchar(50), TIPO_0202 varchar(2), SITUACION varchar(2), Y_ETRS89 float8, TIPO_0504 varchar(2), CATEG_0301 varchar(2), ELECTRIFIC varchar(2), ID_BTN100E float8, COD_ICAO varchar(254), ALT_ORTOM float8, PRODUCTO varchar(2), ANCHO_VIA varchar(2), CODIGO_INE varchar(11), LATITUD varchar(254), UN_LOCODE varchar(5), COMPE varchar(2),
      COD_IATA varchar(254), COD_EST varchar(5), TIPO_0506 varchar(2), TIPO_0311 varchar(2), CATEG_0203 varchar(2), ITIN_EUR varchar(2), TIPO_0503 varchar(2), NUMERO varchar(6), COTA varchar(4), TRAFICO varchar(2), CATEG_0604 varchar(2), COD_BIC varchar(254), TIPO_0702 varchar(2), COMPO_0301 varchar(2), COD_VIA varchar(6), CAPITAL varchar(4), gid serial,PRIKEY, SK varchar(15), TIPO_0705 varchar(2), TIPO_0308 varchar(2), POBLACION float8, COMPE_0613 varchar(2), ENDORREICO varchar(2), TIPO_0615 varchar(2), TIPO_0201 varchar(2), TIPO_0102 varchar(2), COD_RIO varchar(18), COD_0101 varchar(11), CATEG_0202 varchar(2), TIPO_0612 varchar(2),
      TIPO_0302 varchar(2), TIPO_0101 varchar(2), X_ETRS89 float8, NUM_VIAS varchar(2), COMPE_0615 varchar(2), ALT_ELIPS float8, TIPO_0611 varchar(2), TIPO_0310 varchar(2), TIPO_0312 varchar(2), HUSO float8, REGIMEN varchar(2), TEN_T varchar(2), ESTADO varchar(2), TIPO_0607 varchar(2), TIPO_0701 varchar(2), CATEG_1001 varchar(2), INTERNA varchar(2), TIPO_0305 varchar(2), CALZADA varchar(2), TIPO_0203 varchar(2), CATEG_0307 varchar(2), REGENTE varchar(2), ACCESO varchar(2)
    -> SubstringExtractor
SubstringExtractor
    SRC_ATTR = fme_feature_type
    END = -1
    START = 7
    RESULT_ATTR = _substring
    -> GeometryFilter
GeometryFilter
    BREAK_AGG = No
    POINT -> 2DForcer
    LINE -> 2DForcer_2
    AREA -> 2DForcer_3
2DForcer
    2D -> NewFeatureType (writer SHAPE_1)
NewFeatureType (writer SHAPE_1)
2DForcer_2
    2D -> NewFeatureType00 (writer SHAPE_1)
NewFeatureType00 (writer SHAPE_1)
2DForcer_3
    2D -> NewFeatureType01 (writer SHAPE_1)
NewFeatureType01 (writer SHAPE_1)
